module wayang-hardware-dimension {
    yang-version 1.1;
    namespace "urn:bt.com:wayang-hardware-dimension";
    prefix wayang-dimension;
    import ietf-hardware {
        prefix ietfhw;
        revision-date "2018-01-15";
    }
    import wayang-hardware {
        prefix wayanghw;
        revision-date "2018-08-09";
    }

    organization
        "BT";
    contact
        "Paul.M.Jordan@bt.com";
    description               
        "This module enhances wayang-hardware to add optional size, orientation and weight data to componets and component types.
        see https://github.com/pmjordan/wayang/DIMENSION.md";
        
    revision 2018-08-09 {
        description
        "First draft for discussion";
    }


    typedef lengthMeasurementUnits {
        description "The units for depth, height and/or width";
        reference "MeasurementUnits in Hardware section of TM Forum GB922 Physical Resource R17.5 https://www.tmforum.org/resources/suite/gb922-information-framework-models-r17-5-0/";
        /* YANG 'units' keyword is not used as there is then no way to restrict the textual value of the units value to the list enumerated in the reference*/
        type enumeration {  
            enum Unknown {
                description "Can also be used for not measured";
                value 0;
            }
            enum inches {
                value 1;
            }
            enum feet {
                value 2;
            }
            enum millimeters {
                value 3;
            }
            enum centimeters {
                value 4;
            }
            enum meters {
                value 5;
            }  
        }
    }
    typedef angle-unit {
        description "The units for measureing angles";
        type enumeration {  
            enum Unknown {
                value 0;
            }
            enum radians {
                value 1;
            }
            enum degrees {
                value 2;  
            }
        }
        default degrees;
    }

    grouping mass {
        description "The overall weight expressed in the declared units";
            reference "TM Forum GB922 Physical Resource R17.5 https://www.tmforum.org/resources/suite/gb922-information-framework-models-r17-5-0/";
        leaf weight {
            type string;
            description "type is string for consientency with the reference but values expected to be numbers";
            config false;
        }
        leaf weightUnits {
            description "Units for the value of weight";
            config false;
            must '(string-length(weight) >0 and string-length(measurementUnits) > 0) or measurementUnits="Unknown"' {
                description "Must be present if weight is present";
                error-message "Units must be quoted for weight value";
            }
            type enumeration {  
                enum Unknown {
                    description "Can also be used for not measured";
                    value 0;
                }
                enum ounces {
                    value 1;
                }
                enum pounds {
                    value 2;
                }
                enum grams {
                    value 3;
                }
                enum kilograms {
                    value 4;
                }
            }
        }
    }
        
    grouping overall-size {
        description "The overall size measurement in the X (width), Y (height), and Z (depth) axes expressed in the declared units";
            reference "TM Forum GB922 Physical Resource R17.5 https://www.tmforum.org/resources/suite/gb922-information-framework-models-r17-5-0/";
        leaf depth {
            type string;
            description "type is string for consientency with the reference but values expected to be numbers";
            config false;
        }
        leaf height {
            type string;
            description "type is string for consientency with the reference but values expected to be numbers";
            config false;
        }
        leaf measurementUnits {
            description "The units for depth, height and/or width";
            config false;
            type lengthMeasurementUnits;
            must '(string-length(depth) >0 or string-length(height) >0 or string-length(width)>0) and string-length(measurementUnits) > 0' {
                description "Must be present if any one of depth, height or width are present";
                error-message "Units must be quoted for overall size values";
            }
        }
        leaf width {
            type string;
            description "type is string for consientency with the reference but values expected to be numbers";
            config false;
        }
    }
            
    grouping offset {
        description "The distance from one point in space to another point expressed in X,Y and Z coordinates";
        leaf offsetMeasurementUnits {
            type lengthMeasurementUnits;
            description "The units for the units for the X, Y and Z dimensions";
            config false;
            must '(x-offset >= 0 and y-offset >= 0 and z-offset >= 0) and (string-length(offsetMeasurementUnits) > 0) and not(offsetMeasurementUnits="Unknown"))' {
                description "Units must be supplied if offset values are used";
                error-message "Units must be quoted for offset values";
            }
        }
        leaf x-offset {
            type decimal64 {
                /* using a type of number is more appropriate to a distance measurement than string as used in overall-size
                decimal64  is the base YANG type for number*/
                fraction-digits 2;
                /* use of faction-digits is mandatory when using decimal64. Where not appropriate for a particular useage of offset then
                it may be subject of a deviation statement to change it to a more suitable value in that situation*/
            }
            config false;
            must '(x-offset >= 0 and y-offset >= 0 and z-offset >= 0)' {
                description "If offset is used then there must be a value of X,Y and Z";
                error-message "Values must be supplied for all three dimensions of the offset";
            }
        }       
        leaf y-offset {
            type decimal64 {
                fraction-digits 2;
            }
            config false;
        }
        leaf z-offset {
            type decimal64 {
                fraction-digits 2;
            }
            config false;
        }
    }

    grouping orientation {
        description "The spherical coordinates to rotate a component around its origin";
        leaf azimuth {
            type uint8;
            config false;
        }
        leaf orientation-angle-unit {
            type angle-unit;
            config false;
        }
        leaf polar {
            type uint8;
            config false;
        }
        leaf radius {
            description "radius is not required to express orientation and is only included for completeness";
            type uint8;
            config false;
        }       
    }





    augment "/ietfhw:hardware/ietfhw:component" {
        uses overall-size {
            description "The dimensions of the component when installed. 
            For example a card may be installed vertically or horizontally and so XY and Z values from the
            component-type may be used in a different order when instantiated as a component.
            If installed off-axis the values will also change.";
        }
        uses mass;
        container offset-from-parent {
            description "The distance from the origin of the parent component to the origin of the this component.
            The origin is where the overall measurement axes meet at zero 
            i.e. front, bottom, left of the cuboid which encloses the component";
            uses offset;
        }
        container orientation {
            description "Used to describe how a component is installed in its parent
            Not required if the depth, height and width defined by the component-type size
            correspond to the X,Y and Z dimensions when installed. 
            The spherical coordinates to transform the orientation of the component-type to the installed postion.
            For example a card-type defined vertically but installed horizontaly would have a value of
            polar=0, azimuth=-90, r=1 ,
            a card installed in a rear facing slot would have values of
            polar=180, azimuth=0, r=1";
            uses orientation;
        }
    }
    
    augment "/ietfhw:hardware/wayanghw:component-type" {
        uses overall-size {
            description "The dimensions of components of this type. 
            The choice of which dimension to record as depth, height and width should reflect 
            the orientation expected to be most common when components of this type are installed";
            }
        uses mass {
            description "The weight of components of this type";
        }
    }

    augment "/ietfhw:hardware/wayanghw:component-type/wayanghw:includes-child-type" {
        container included-child-offset-from-parent {
            description "The distance from the origin of the parent component to the origin of the 
            included child component.
            The origin is where the overall measurement axes meet at zero 
            i.e. front, bottom, left of the cuboid which encloses the component";
            uses offset;
        }
        container included-child-orientation {
            description "Only required when included child is orientated off the X,Y,Z axis
            applies a rotation to the size values";
            uses orientation;
        }
    }
}
